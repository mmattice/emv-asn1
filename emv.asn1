EMV DEFINITIONS IMPLICIT TAGS::=

BEGIN

 IssuerIdentificationNumber                               ::= [APPLICATION      2] OCTET STRING           -- 42 SIMPLE n 6
 ApplicationDedicatedFileName                             ::= [APPLICATION     15] OCTET STRING           -- 4F SIMPLE b
 ApplicationLabel                                         ::= [APPLICATION     16] OCTET STRING           -- 50 SIMPLE ans with the special character limited to space
 Track2EquivalentData                                     ::= [APPLICATION     23] OCTET STRING           -- 57 SIMPLE b n, var. up to 19 b n 4 n 3 n, var. b
 ApplicationPrimaryAccountNumber                          ::= [APPLICATION     26] OCTET STRING           -- 5A SIMPLE cn  var. up to 19
 CardholderName                                           ::= [APPLICATION    160] OCTET STRING           -- 5F20 SIMPLE ans 2-26
 ApplicationExpirationDate                                ::= [APPLICATION    164] OCTET STRING           -- 5F24 SIMPLE n 6 YYMMDD
 IssuerCountryCode                                        ::= [APPLICATION    168] OCTET STRING           -- 5F28 SIMPLE n 3
 TransactionCurrencyCode                                  ::= [APPLICATION    170] OCTET STRING           -- 5F2A SIMPLE n 3
 LanguagePreference                                       ::= [APPLICATION    173] OCTET STRING           -- 5F2D SIMPLE an 2
 ServiceCode                                              ::= [APPLICATION    176] OCTET STRING           -- 5F30 SIMPLE n 3
 ApplicationPrimaryAccountNumberSequenceNumber            ::= [APPLICATION    180] OCTET STRING           -- 5F34 SIMPLE n 2
 TransactionCurrencyExponent                              ::= [APPLICATION    182] OCTET STRING           -- 5F36 SIMPLE n 1
 IssuerURL                                                ::= [APPLICATION    208] OCTET STRING           -- 5F50 SIMPLE ans
 InternationalBankAccountNumber                           ::= [APPLICATION    211] OCTET STRING           -- 5F53 SIMPLE var.
 BankIdentifierCode                                       ::= [APPLICATION    212] OCTET STRING           -- 5F54 SIMPLE var.
 IssuerCountryCodeAlpha2format                            ::= [APPLICATION    213] OCTET STRING           -- 5F55 SIMPLE a 2
 IssuerCountryCodeAlpha3format                            ::= [APPLICATION    214] OCTET STRING           -- 5F56 SIMPLE a 3
 AccountType                                              ::= [APPLICATION    215] OCTET STRING           -- 5F57 SIMPLE n 2 
 ResponseMessageTemplateFormat1                           ::= [                 0] OCTET STRING           -- 80 SIMPLE var.
 AmountAuthorisedBinary                                   ::= [                 1] OCTET STRING           -- 81 SIMPLE b 
 ApplicationInterchangeProfile                            ::= [                 2] OCTET STRING           -- 82 SIMPLE b
 CommandTemplate                                          ::= [                 3] OCTET STRING           -- 83 SIMPLE b
 DedicatedFileName                                        ::= [                 4] OCTET STRING           -- 84 SIMPLE b
 IssuerScriptCommand                                      ::= [                 6] OCTET STRING           -- 86 SIMPLE b
 ApplicationPriorityIndicator                             ::= [                 7] OCTET STRING           -- 87 SIMPLE b
 ShortFileIdentifier                                      ::= [                 8] OCTET STRING           -- 88 SIMPLE b
 AuthorisationCode                                        ::= [                 9] OCTET STRING           -- 89 SIMPLE As defined by the Payment Systems
 AuthorisationResponseCode                                ::= [                10] OCTET STRING           -- 8A SIMPLE an 2
 CardRiskManagementDataObjectList1                        ::= [                12] OCTET STRING           -- 8C SIMPLE b
 CardRiskManagementDataObjectList2                        ::= [                13] OCTET STRING           -- 8D SIMPLE b
 CardholderVerificationMethodList                         ::= [                14] OCTET STRING           -- 8E SIMPLE b
 CertificationAuthorityPublicKeyIndex                     ::= [                15] OCTET STRING           -- 8F SIMPLE b
 IssuerPublicKeyCertificate                               ::= [                16] OCTET STRING           -- 90 SIMPLE b
 IssuerAuthenticationData                                 ::= [                17] OCTET STRING           -- 91 SIMPLE b
 IssuerPublicKeyRemainder                                 ::= [                18] OCTET STRING           -- 92 SIMPLE b
 SignedStaticApplicationData                              ::= [                19] OCTET STRING           -- 93 SIMPLE b
 ApplicationFileLocator                                   ::= [                20] OCTET STRING           -- 94 SIMPLE var.
 TerminalVerificationResults                              ::= [                21] OCTET STRING           -- 95 SIMPLE b
 TransactionCertificateDataObjectList                     ::= [                23] OCTET STRING           -- 97 SIMPLE b
 TransactionCertificateHashValue                          ::= [                24] OCTET STRING           -- 98 SIMPLE b
 TransactionPersonalIdentificationNumberData              ::= [                25] OCTET STRING           -- 99 SIMPLE b
 TransactionDate                                          ::= [                26] OCTET STRING           -- 9A SIMPLE n 6 YYMMDD
 TransactionStatusInformation                             ::= [                27] OCTET STRING           -- 9B SIMPLE b
 TransactionType                                          ::= [                28] OCTET STRING           -- 9C SIMPLE n 2
 DirectoryDefinitionFileName                              ::= [                29] OCTET STRING           -- 9D SIMPLE b
 AcquirerIdentifier                                       ::= [               129] OCTET STRING           -- 9F01 SIMPLE n 6-11 
 AmountAuthorised                                         ::= [               130] OCTET STRING           -- 9F02 SIMPLE n 12
 AmountOther                                              ::= [               131] OCTET STRING           -- 9F03 SIMPLE n 12
 AmountOtherBinary                                        ::= [               132] OCTET STRING           -- 9F04 SIMPLE b
 ApplicationDiscretionaryData                             ::= [               133] OCTET STRING           -- 9F05 SIMPLE b
 ApplicationIdentifier-terminal                           ::= [               134] OCTET STRING           -- 9F06 SIMPLE b
 ApplicationUsageControl                                  ::= [               135] OCTET STRING           -- 9F07 SIMPLE b 
 ApplicationVersionNumberICC                              ::= [               136] OCTET STRING           -- 9F08 SIMPLE b 
 ApplicationVersionNumberTerminal                         ::= [               137] OCTET STRING           -- 9F09 SIMPLE b 
 CardholderNameExtended                                   ::= [               139] OCTET STRING           -- 9F0B SIMPLE ans 27-45
 IssuerActionCode-Default                                 ::= [               141] OCTET STRING           -- 9F0D SIMPLE b
 IssuerActionCode-Denial                                  ::= [               142] OCTET STRING           -- 9F0E SIMPLE b
 IssuerActionCode-Online                                  ::= [               143] OCTET STRING           -- 9F0F SIMPLE b
 IssuerApplicationData                                    ::= [               144] OCTET STRING           -- 9F10 SIMPLE b
 IssuerCodeTableIndex                                     ::= [               145] OCTET STRING           -- 9F11 SIMPLE n 2
 ApplicationPreferredName                                 ::= [               146] OCTET STRING           -- 9F12 SIMPLE ans (see section 4.3)
 LastOnlineApplicationTransactionCounterRegister          ::= [               147] OCTET STRING           -- 9F13 SIMPLE b
 LowerConsecutiveOfflineLimit                             ::= [               148] OCTET STRING           -- 9F14 SIMPLE b
 MerchantCategoryCode                                     ::= [               149] OCTET STRING           -- 9F15 SIMPLE n 4
 MerchantIdentifier                                       ::= [               150] OCTET STRING           -- 9F16 SIMPLE ans 15
 PersonalIdentificationNumberTryCounter                   ::= [               151] OCTET STRING           -- 9F17 SIMPLE b
 IssuerScriptIdentifier                                   ::= [               152] OCTET STRING           -- 9F18 SIMPLE b
 TerminalCountryCode                                      ::= [               154] OCTET STRING           -- 9F1A SIMPLE n 3
 TerminalFloorLimit                                       ::= [               155] OCTET STRING           -- 9F1B SIMPLE b
 TerminalIdentification                                   ::= [               156] OCTET STRING           -- 9F1C SIMPLE an 8
 TerminalRiskManagementData                               ::= [               157] OCTET STRING           -- 9F1D SIMPLE b
 InterfaceDeviceSerialNumber                              ::= [               158] OCTET STRING           -- 9F1E SIMPLE an 8
 Track1DiscretionaryData                                  ::= [               159] OCTET STRING           -- 9F1F SIMPLE ans
 Track2DiscretionaryData                                  ::= [               160] OCTET STRING           -- 9F20 SIMPLE cn
 TransactionTime                                          ::= [               161] OCTET STRING           -- 9F21 SIMPLE n 6 HHMMSS
 CertificationAuthorityPublicKeyIndex                     ::= [               162] OCTET STRING           -- 9F22 SIMPLE b
 UpperConsecutiveOfflineLimit                             ::= [               163] OCTET STRING           -- 9F23 SIMPLE b
 ApplicationCryptogram                                    ::= [               166] OCTET STRING           -- 9F26 SIMPLE b
 CryptogramInformationData                                ::= [               167] OCTET STRING           -- 9F27 SIMPLE b
 IntegratedCircuitCardPINEnciphermentPublicKeyCertificate ::= [               173] OCTET STRING           -- 9F2D SIMPLE b
 IntegratedCircuitCardPINEnciphermentPublicKeyExponent    ::= [               174] OCTET STRING           -- 9F2E SIMPLE b
 IntegratedCircuitCardPINEnciphermentPublicKeyRemainder   ::= [               175] OCTET STRING           -- 9F2F SIMPLE b
 IssuerPublicKeyExponent                                  ::= [               178] OCTET STRING           -- 9F32 SIMPLE b
 TerminalCapabilities                                     ::= [               179] OCTET STRING           -- 9F33 SIMPLE b
 CardholderVerificationMethodResults                      ::= [               180] OCTET STRING           -- 9F34 SIMPLE b
 TerminalType                                             ::= [               181] OCTET STRING           -- 9F35 SIMPLE n 2
 ApplicationTransactionCounter                            ::= [               182] OCTET STRING           -- 9F36 SIMPLE b 
 UnpredictableNumber                                      ::= [               183] OCTET STRING           -- 9F37 SIMPLE b
 ProcessingOptionsDataObjectList                          ::= [               184] OCTET STRING           -- 9F38 SIMPLE b
 Point-of-ServiceEntryMode                                ::= [               185] OCTET STRING           -- 9F39 SIMPLE n 2
 AmountReferenceCurrency                                  ::= [               186] OCTET STRING           -- 9F3A SIMPLE b
 ApplicationReferenceCurrency                             ::= [               187] OCTET STRING           -- 9F3B SIMPLE n 3
 TransactionReferenceCurrencyCode                         ::= [               188] OCTET STRING           -- 9F3C SIMPLE n 3
 TransactionReferenceCurrencyExponent                     ::= [               189] OCTET STRING           -- 9F3D SIMPLE n 1
 AdditionalTerminalCapabilities                           ::= [               192] OCTET STRING           -- 9F40 SIMPLE b 
 TransactionSequenceCounter                               ::= [               193] OCTET STRING           -- 9F41 SIMPLE n 4-8
 ApplicationCurrencyCode                                  ::= [               194] OCTET STRING           -- 9F42 SIMPLE n 3
 ApplicationReferenceCurrencyExponent                     ::= [               195] OCTET STRING           -- 9F43 SIMPLE n 1
 ApplicationCurrencyExponent                              ::= [               196] OCTET STRING           -- 9F44 SIMPLE n 1
 DataAuthenticationCode                                   ::= [               197] OCTET STRING           -- 9F45 SIMPLE b
 IntegratedCircuitCardPublicKeyCertificate                ::= [               198] OCTET STRING           -- 9F46 SIMPLE b
 IntegratedCircuitCardPublicKeyExponent                   ::= [               199] OCTET STRING           -- 9F47 SIMPLE b
 IntegratedCircuitCardPublicKeyRemainder                  ::= [               200] OCTET STRING           -- 9F48 SIMPLE b
 DynamicDataAuthenticationDataObjectList                  ::= [               201] OCTET STRING           -- 9F49 SIMPLE b
 StaticDataAuthenticationTagList                          ::= [               202] OCTET STRING           -- 9F4A SIMPLE —
 SignedDynamicApplicationData                             ::= [               203] OCTET STRING           -- 9F4B SIMPLE b
 ICCDynamicNumber                                         ::= [               204] OCTET STRING           -- 9F4C SIMPLE b
 LogEntry                                                 ::= [               205] OCTET STRING           -- 9F4D SIMPLE b
 MerchantNameandLocation                                  ::= [               206] OCTET STRING           -- 9F4E SIMPLE ans
 LogFormat                                                ::= [               207] OCTET STRING           -- 9F4F SIMPLE b
 TransactionCategoryCode                                  ::= [               211] OCTET STRING           -- 9F53 SIMPLE an
 FileControlInformationProprietaryTemplate                ::= [                 5] EXPLICIT OCTET STRING  -- A5 CONSTRUCTED var.
 FileControlInformationIssuerDiscretionaryData            ::= [               140] EXPLICIT OCTET STRING  -- BF0C CONSTRUCTED var.
 ApplicationTemplate                                      ::= [APPLICATION      1] EXPLICIT OCTET STRING  -- 61 CONSTRUCTED b
 FileControlInformationTemplate                           ::= [APPLICATION     15] EXPLICIT OCTET STRING  -- 6F CONSTRUCTED var.
 READRECORDResponseMessageTemplate                        ::= [APPLICATION     16] EXPLICIT OCTET STRING  -- 70 CONSTRUCTED var.
 IssuerScriptTemplate1                                    ::= [APPLICATION     17] SEQUENCE {             -- 71 CONSTRUCTED b
    issuerscriptidentifier IssuerScriptIdentifier,
    issuerscriptcommand    IssuerScriptCommand
 }
 IssuerScriptTemplate2                                    ::= [APPLICATION     18] SEQUENCE {             -- 72 CONSTRUCTED b
    issuerscriptidentifier IssuerScriptIdentifier,
    issuerscriptcommand    IssuerScriptCommand
 }
 DirectoryDiscretionaryTemplate                           ::= [APPLICATION     19] EXPLICIT OCTET STRING  -- 73 CONSTRUCTED var.
 ResponseMessageTemplateFormat2                           ::= [APPLICATION     23] EXPLICIT OCTET STRING  -- 77 CONSTRUCTED var.

END
